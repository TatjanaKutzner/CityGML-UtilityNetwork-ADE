FME workspace water_pipes.fmw

Parameters:
- DestDataset_CITYGML = /media/isaac/Data/EIFER/Nanaimo_Network_Modeling/local_git/CityGML-UtilityNetwork-ADE/Sample/Nanaimo_Water_Network/data_out/nanaimo_water_pipes.gml   # Destination CityGML Document
- SourceDataset_GEOTIFF = /media/isaac/Data/EIFER/Nanaimo_Network_Modeling/data_in/Nanaimo_DEM1.tif   # Source GeoTIFF File(s)
- SourceDataset_ESRISHAPE_7 = /media/isaac/Data/EIFER/Nanaimo_Network_Modeling/local_git/CityGML-UtilityNetwork-ADE/Sample/Nanaimo_Water_Network/data_in/Pipes/PIPES_AND_SERVICES_sm.shp   # Source Esri Shapefile(s)
- SourceDataset_ESRISHAPE = /media/isaac/Data/EIFER/Nanaimo_Network_Modeling/local_git/CityGML-UtilityNetwork-ADE/Sample/Nanaimo_Water_Network/data_in/Pipes/PARCELS_sm.shp   # Source Esri Shapefile(s)
- SourceDataset_GEOTIFF_3 = /media/isaac/Data/EIFER/Nanaimo_Network_Modeling/local_git/CityGML-UtilityNetwork-ADE/Sample/Nanaimo_Water_Network/data_in/DEM/Nanaimo_DEM1.tif   # Source GeoTIFF File(s)

Readers:
- GEOTIFF_1: GEOTIFF from $(SourceDataset_GEOTIFF)
- ESRISHAPE_1: ESRISHAPE from $(SourceDataset_ESRISHAPE_7)
- ESRISHAPE_2: ESRISHAPE from $(SourceDataset_ESRISHAPE)
- GEOTIFF_2: GEOTIFF from $(SourceDataset_GEOTIFF_3)

Writers:
- CITYGML_1: CITYGML to $(DestDataset_CITYGML)

AttributeFilter_2
    ATTR_VALUES = <Empty>,<Missing>,<Null>,<Unfiltered>,Service Line
    ATTR_NAME = TYPE
    Service Line -> AttributeValueMapper_4
Network (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_role_in_network{}.xlink_href xml_buffer, utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer,
      utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer, utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer,
      utility_medium_supply{}.utility_optical_medium_supply_utility_storage{}.utility_storage_utility_outflow_rate xml_real64, utility_medium_supply{}.utility_optical_medium_supply_utility_storage{}.utility_storage_utility_outflow_rate_units xml_buffer, utility_medium_supply{}.utility_optical_medium_supply_utility_type xml_char(7), utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer, utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_medium_supply{}.utility_electrical_medium_supply_utility_potential_supply_utility_supply_utility_flow_rate xml_real64, utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer,
      utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29), utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64, utility_medium_supply{}.utility_gaseous_medium_supply_utility_storage{}.utility_storage_utility_inflow_rate_units xml_buffer, utility_medium_supply{}.utility_gaseous_medium_supply_utility_storage{}.utility_storage_utility_outflow_rate xml_real64, utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_class xml_buffer, utility_class_codeSpace xml_buffer, utility_function{} xml_buffer, utility_function{}.codeSpace xml_buffer, utility_usage{} xml_buffer, utility_usage{}.codeSpace xml_buffer, utility_transported_medium_xlink_href xml_buffer,
      utility_sub_network{}.xlink_href xml_buffer, utility_topo_graph_xlink_href xml_buffer, utility_component{}.xlink_href xml_buffer, utility_supplies_xlink_href xml_buffer, utility_sub_ordinate_network{}.xlink_href xml_buffer, utility_super_ordinate_network{}.xlink_href xml_buffer
LiquidMedium (writer CITYGML_1)
    attributes: citygml_target_uri xml_buffer, citygml_feature_role xml_buffer, citygml_feature_role_attr_name xml_buffer, citygml_feature_role_attr_val xml_buffer, gml_description xml_buffer, gml_name xml_buffer, utility_owner xml_buffer, utility_is_classified_by{}.xlink_href xml_buffer, utility_associated_network{}.xlink_href xml_buffer, utility_type xml_buffer, utility_type_codeSpace xml_buffer, utility_is_corrosive xml_boolean, utility_is_explosive xml_boolean, utility_flammable xml_real64, utility_electric_conductivity xml_buffer, utility_electric_conductivity_units xml_buffer, utility_ph_value_range xml_buffer, utility_ph_value_range_units xml_buffer, utility_temperature_range xml_buffer, utility_temperature_range_units xml_buffer, utility_flow_rate_range xml_buffer, utility_flow_rate_range_units xml_buffer, utility_pressure_range xml_buffer, utility_pressure_range_units xml_buffer
NetworkGraph (writer CITYGML_1)
    attributes: citygml_target_uri xml_buffer, citygml_feature_role xml_buffer, citygml_feature_role_attr_name xml_buffer, citygml_feature_role_attr_val xml_buffer, gml_description xml_buffer, gml_name xml_buffer, utility_feature_graph_member{}.xlink_href xml_buffer, utility_link_member{}.xlink_href xml_buffer, utility_network_link_member{}.xlink_href xml_buffer
ExteriorMaterial (writer CITYGML_1)
    attributes: citygml_target_uri xml_buffer, citygml_feature_role xml_buffer, citygml_feature_role_attr_name xml_buffer, citygml_feature_role_attr_val xml_buffer, gml_description xml_buffer, gml_name xml_buffer, utility_type xml_buffer, utility_type_codeSpace xml_buffer, utility_consists_of_fm{}.xlink_href xml_buffer, utility_consists_of{}.xlink_href xml_buffer, utility_is_classified_by{}.xlink_href xml_buffer, utility_used_by{}.xlink_href xml_buffer
Note: Rename Node_ID to TerminalEement_Node_ID
AttributeRenamer_26
    ATTR_TABLE = RENAME_SET_DEFAULT Node_ID > RoundPipe_Node_ID
    -> NeighborFinder [CANDIDATE]
Note: Remove geometry because it / is irrelevant for FeatureGraphs
GeometryRemover_2
    -> AttributeCreator_18
    -> FeatureMerger_16 [SUPPLIER]
Note: Set relationship between NetworkGraph / and FeatureGraph (+featureGraphMember)
AttributeCreator_18
    ATTR_TABLE = SET_TO citygml_feature_role = featureGraphMember
    -> AttributeRenamer_21
Note: Set FeatureGraphID as gml_id and / NetworkGraphID as gml_parent_id
AttributeRenamer_21
    ATTR_TABLE:
      RENAME_SET_DEFAULT FeatureGraph_ID > gml_id
      RENAME_SET_DEFAULT NetworkGraph_ID > gml_parent_id
    -> FeatureGraph (writer CITYGML_1)
FeatureGraph (writer CITYGML_1)
    attributes: citygml_target_uri xml_buffer, citygml_feature_role xml_buffer, citygml_feature_role_attr_name xml_buffer, citygml_feature_role_attr_val xml_buffer, gml_description xml_buffer, gml_name xml_buffer, utility_link_member{}.xlink_href xml_buffer, utility_node_member{}.xlink_href xml_buffer
Note: Set relationship between RoundPipe / and Network (+component)
AttributeCreator_22
    ATTR_TABLE = SET_TO citygml_feature_role = component
    -> AttributeRenamer_19
    -> FeatureMerger_16 [REQUESTOR]
FeatureMerger_16
    MERGE_TYPE = Attributes Only
    SUPPLIERS_FIRST = No
    IGNORE_NULLS = No
    PROCESS_DUPS = No
    REJECT_NULL_MISSING_KEYS = No
    JOIN_KEYS = @Value(RoundPipe_ID) @Value(RoundPipe_ID) AUTO
    ATTR_ACCUM_MODE = Merge Supplier
    ATTR_CONFLICT_RES = Use Requestor
    MERGED -> AttributeRenamer_30
Note: Set gml_id = RoundPipe_ID, / gml_parent_id = NetworkID / and xlink = FeatureGraphID
AttributeRenamer_30
    ATTR_TABLE:
      RENAME_SET_DEFAULT FeatureGraph_ID > utility_topo_graph_xlink_href
      RENAME_SET_DEFAULT RoundPipe_ID > gml_id
      RENAME_SET_DEFAULT Network_ID > gml_parent_id
    -> AttributeCreator_15
Note: Set gml_name to be the PID from / the source data and gml_description / to be the street address
AttributeCreator_15
    ATTR_TABLE:
      SET_TO gml_description = @Value(HOUSENUMBE) @Value(STREETNAME) @Value(POSTALCODE)
      SET_TO gml_name = @Value(PID)
      SET_TO YEAR = @Value(utility_year_of_construction)
      SET_TO ACCURACY = @Value(utility_location_quality)
    -> RoundPipe (writer CITYGML_1)
Note: Set TerminalElementID as gml_id / and NetworkID as gml_parent_id
AttributeRenamer_19
    ATTR_TABLE:
      RENAME_SET_DEFAULT Network_ID > gml_parent_id
      RENAME_SET_DEFAULT RoundPipe_ID > gml_id
Note: 1. Each node contains a list which lists all lines (i.e. the corresponding arc_ids) that are connected with the node. / This list is split up here so that each node is connected to one line only. / The number of nodes duplicates analogously to the number of lines connected with a node.
ListExploder_3
    ATTR_ACCUM_MODE = Merge Incoming List
    LIST_ATTR = _node_angle{}
    ATTR_CONFLICT_RES = Use Incoming List
    INDEX_ATTR = _element_index
    ELEMENTS -> ExpressionEvaluator_2
Note: Arc_ids with a negative sign are / turned into positive numbers here.
ExpressionEvaluator_2
    ATTRLIST = fme_arc_id
    ACTION = Overwrite Existing Attributes
    EXPRESSION = @abs(@Value(fme_arc_id))
    -> UUIDGenerator_11
Note: Connect InteriorFeatureLinks with Nodes. / Now InteriorFeatureLinks have attributes of Nodes / So InteriorFeatureLinks can have a reference to a start Node
FeatureMerger_10
    MERGE_TYPE = Attributes Only
    SUPPLIERS_FIRST = No
    IGNORE_NULLS = No
    PROCESS_DUPS = No
    REJECT_NULL_MISSING_KEYS = No
    JOIN_KEYS = @Value(_edge_id) @Value(fme_arc_id) AUTO @Value(_from_node) @Value(_node_number) AUTO
    ATTR_ACCUM_MODE = Merge Supplier
    ATTR_CONFLICT_RES = Use Requestor
    MERGED -> AttributeRenamer_15
Note: Set XLink reference between / InteriorFeatureLink and start / nodes
AttributeRenamer_15
    ATTR_TABLE = RENAME_SET_DEFAULT Node_ID > utility_start_xlink_href
    -> FeatureMerger_11 [REQUESTOR]
Note: Connect InteriorFeatureLinks with Nodes. / Now InteriorFeatureLinks have attributes of Nodes / So InteriorFeatureLinks can have a reference to a end Node
FeatureMerger_11
    MERGE_TYPE = Attributes Only
    SUPPLIERS_FIRST = No
    IGNORE_NULLS = No
    PROCESS_DUPS = No
    REJECT_NULL_MISSING_KEYS = No
    JOIN_KEYS = @Value(_edge_id) @Value(fme_arc_id) AUTO @Value(_to_node) @Value(_node_number) AUTO
    ATTR_ACCUM_MODE = Merge Supplier
    ATTR_CONFLICT_RES = Use Requestor
    MERGED -> AttributeRenamer_16
Note: Set XLink reference between / InteriorFeatureLink and end / nodes
AttributeRenamer_16
    ATTR_TABLE = RENAME_SET_DEFAULT Node_ID > utility_end_xlink_href
    -> 3DForcer_4
    -> FeatureMerger_13 [SUPPLIER]
    -> FeatureMerger_12 [SUPPLIER]
Note: Set relationship between InterFeatureLink / and NetworkGraph (+linkMember)
AttributeCreator_13
    ATTR_TABLE = SET_TO citygml_feature_role = linkMember
    -> AttributeRenamer_17
Note: Set gml_id (InteriorFeatureLink ID) / Also set gml_parent_id (FeatureGraph)
AttributeRenamer_17
    ATTR_TABLE:
      RENAME_SET_DEFAULT InteriorFeatureLink_ID > gml_id
      RENAME_SET_DEFAULT FeatureGraph_ID > gml_parent_id
    -> InteriorFeatureLink (writer CITYGML_1)
InteriorFeatureLink (writer CITYGML_1)
    attributes: citygml_target_uri xml_buffer, citygml_feature_role xml_buffer, citygml_feature_role_attr_name xml_buffer, citygml_feature_role_attr_val xml_buffer, gml_description xml_buffer, gml_name xml_buffer, utility_direction xml_char(1), utility_link_control xml_xml, utility_start_xlink_href xml_buffer, utility_end_xlink_href xml_buffer
FeatureMerger_13
    MERGE_TYPE = Attributes Only
    SUPPLIERS_FIRST = No
    IGNORE_NULLS = No
    PROCESS_DUPS = No
    REJECT_NULL_MISSING_KEYS = No
    JOIN_KEYS = @Value(Node_ID) @Value(utility_end_xlink_href) AUTO
    ATTR_ACCUM_MODE = Merge Supplier
    ATTR_CONFLICT_RES = Use Requestor
    MERGED -> AttributeCreator_23
    NOT_MERGED -> FeatureMerger_12 [REQUESTOR]
FeatureMerger_12
    MERGE_TYPE = Attributes Only
    SUPPLIERS_FIRST = No
    IGNORE_NULLS = No
    PROCESS_DUPS = No
    REJECT_NULL_MISSING_KEYS = No
    JOIN_KEYS = @Value(Node_ID) @Value(utility_start_xlink_href) AUTO
    ATTR_ACCUM_MODE = Merge Supplier
    ATTR_CONFLICT_RES = Use Requestor
    MERGED -> AttributeCreator_23
Note: Set type = exterior
AttributeCreator_23
    ATTR_TABLE:
      SET_TO citygml_feature_role = nodeMember
      SET_TO utility_type = exterior
    -> 3DForcer_5
Note: Set relation between FeatureGraph / and Node (+nodeMember)
AttributeCreator_16
    ATTR_TABLE = SET_TO citygml_feature_role = nodeMember
    -> AttributeRenamer_18
Note: Set gml_id to Node_ID / and gml_parent_id to FeatureGraph_ID
AttributeRenamer_18
    ATTR_TABLE:
      RENAME_SET_DEFAULT Node_ID > gml_id
      RENAME_SET_DEFAULT FeatureGraph_ID > gml_parent_id
    -> Node (writer CITYGML_1)
Node (writer CITYGML_1)
    attributes: citygml_target_uri xml_buffer, citygml_feature_role xml_buffer, citygml_feature_role_attr_name xml_buffer, citygml_feature_role_attr_val xml_buffer, gml_description xml_buffer, gml_name xml_buffer, utility_type xml_char(8), utility_connection_signature xml_xml, utility_link_control xml_xml
Note: Rename Node_ID to TerminalEement_Node_ID
AttributeRenamer_27
    ATTR_TABLE = RENAME_SET_DEFAULT Node_ID > TerminalElement_Node_ID
    -> NeighborFinder [BASE]
Note: Set RoundPipe_Node_ID as utility_start_xlink_href / and TerminalElement_Node_ID as utility_start_xlink_href
AttributeRenamer_29
    ATTR_LIST = RoundPipe_Node_ID,utility_start_xlink_href,,TerminalElement_Node_ID,utility_end_xlink_href,
    -> GeometryRemover_4
Note: Remove geometry because it is irrelevant / for an InterFeatureLink
GeometryRemover_4
    -> AttributeCreator_21
Note: Set utility_type = connects
AttributeCreator_21
    ATTR_TABLE = SET_TO utility_type = connects
    -> AttributeCreator_20
Note: Set relationship between FeatureGraph / and InterFeatureLink (+linkMember)
AttributeCreator_20
    ATTR_LIST = citygml_feature_role,linkMember
    -> AttributeRenamer_28
Note: Set gml_id to InterFeatureLink_ID / and gml_parent_id to NetworkGraph_ID
AttributeRenamer_28
    ATTR_LIST = InterFeatureLink_ID,gml_id,,NetworkGraph_ID,gml_parent_id,
    -> InterFeatureLink (writer CITYGML_1)
InterFeatureLink (writer CITYGML_1)
    attributes: citygml_target_uri xml_buffer, citygml_feature_role xml_buffer, citygml_feature_role_attr_name xml_buffer, citygml_feature_role_attr_val xml_buffer, gml_description xml_buffer, gml_name xml_buffer, utility_direction xml_char(1), utility_link_control xml_xml, utility_start_xlink_href xml_buffer, utility_end_xlink_href xml_buffer, utility_type xml_char(8)
RoundPipe (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_role_in_network{}.xlink_href xml_buffer, utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer,
      utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer, utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer,
      utility_medium_supply{}.utility_optical_medium_supply_utility_storage{}.utility_storage_utility_outflow_rate xml_real64, utility_medium_supply{}.utility_optical_medium_supply_utility_storage{}.utility_storage_utility_outflow_rate_units xml_buffer, utility_medium_supply{}.utility_optical_medium_supply_utility_type xml_char(7), utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer, utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_medium_supply{}.utility_electrical_medium_supply_utility_potential_supply_utility_supply_utility_flow_rate xml_real64, utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer,
      utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29), utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64, utility_medium_supply{}.utility_gaseous_medium_supply_utility_storage{}.utility_storage_utility_inflow_rate_units xml_buffer, utility_medium_supply{}.utility_gaseous_medium_supply_utility_storage{}.utility_storage_utility_outflow_rate xml_real64, utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_function xml_buffer, utility_function_codeSpace xml_buffer, utility_usage{} xml_buffer, utility_usage{}.codeSpace xml_buffer, utility_connected_city_object xml_buffer, utility_year_of_construction xml_date, utility_status xml_char(16),
      utility_location_quality xml_char(12), utility_elevation_quality xml_char(12), utility_consists_of{}.xlink_href xml_buffer, utility_has_material{}.xlink_href xml_buffer, utility_topo_graph_xlink_href xml_buffer, utility_occupied_hollow_space_xlink_href xml_buffer, citygml_level_of_detail{} xml_buffer, utility_class xml_buffer, utility_class_codeSpace xml_buffer, utility_function_of_line xml_buffer, utility_function_of_line_codeSpace xml_buffer, utility_is_gravity xml_boolean, utility_exterior_width xml_real64, utility_exterior_width_units xml_buffer, utility_exterior_height xml_real64, utility_exterior_height_units xml_buffer, utility_exterior_diameter xml_real64, utility_exterior_diameter_units xml_buffer, utility_interior_diameter xml_real64, utility_interior_diameter_units xml_buffer

Bookmark: Read Services and Parcels source data and make (near) vertical lines that come from undergorund up to the building above
PARCELS_sm (reader ESRISHAPE_2)
    attributes: TYPE char(20), HOUSENUMBE char(20), STREETNAME char(50), POSTALCODE char(10), ACCURACY char(25), STATUS char(10), AREA number(31,15), PLAN char(20), PID char(20), GISLINK char(20), GID number(11,0), ZONING1 char(30), ZONE1_DESC char(100), ZONING2 char(30), ZONE2_DESC char(100), ZONING3 char(30), ZONE3_DESC char(100), ZONING4 char(30), ZONE4_DESC char(100)
    -> UUIDGenerator_9
UUIDGenerator_9
    UUID_ATTR = Parcel_UUID
    -> PointOnAreaOverlayer [AREA]
GEOTIFF (reader GEOTIFF_2)
    attributes: datatype char(255)
    -> SurfaceDraper_2 [POINTS/LINES]
Note: Extract nodes from the Service Lines source data
TopologyBuilder_2
    DEAGGREGATE_INPUT = Yes
    BOUNDING_EDGES = All
    OVERLAPPING_MODE = No
    ALLOW_CYCLES = No
    MAX = 0
    PROP_ATTRS = No
    CLEAN_DATA = No
    NODE -> PointOnAreaOverlayer [POINT]
Note: Overlay the node with the Parcel / source data
PointOnAreaOverlayer
    DEAGGREGATE_INPUT = Yes
    ATTR_ACCUM_MODE = Merge Incoming
    OV_ATTR = _overlaps
    ATTR_CONFLICT_RES = Use Original
    POLYS_FIRST = No
    POINT -> AttributeFilter
Note: Remove all features without / a PID
AttributeFilter
    ATTR_VALUES = <EMPTY>,<MISSING>,<NULL>,<UNFILTERED>
    ATTR_NAME = PID
    <UNFILTERED> -> FeatureMerger_9 [REQUESTOR]
Note: Connect features to Network / NetworkGraph
FeatureMerger_9
    MERGE_TYPE = Attributes Only
    SUPPLIERS_FIRST = No
    IGNORE_NULLS = No
    PROCESS_DUPS = No
    REJECT_NULL_MISSING_KEYS = No
    JOIN_KEYS = 1 1 AUTO
    ATTR_ACCUM_MODE = Merge Supplier
    ATTR_CONFLICT_RES = Use Requestor
    MERGED -> SurfaceDraper_2 [DRAPE_FEATURES]
AttributeRenamer_20
    ATTR_TABLE:
      RENAME_SET_DEFAULT YEAR > utility_year_of_construction
      RENAME_SET_DEFAULT ACCURACY > utility_location_quality
    -> TopologyBuilder_3
TopologyBuilder_3
    DEAGGREGATE_INPUT = Yes
    BOUNDING_EDGES = All
    OVERLAPPING_MODE = No
    ALLOW_CYCLES = No
    MAX = 0
    PROP_ATTRS = No
    CLEAN_DATA = Yes
    NODE -> ListExploder_3
    LINE -> UUIDGenerator_12

Bookmark: Read source data, remap attributes and build topology
PIPES_AND_SERVICES_sm (reader ESRISHAPE_1)
    attributes: TYPE char(20), DIAMETER number(11,0), MATERIAL char(20), WATERCATEG char(20), CATCHMENT char(50), OWNER char(20), YEAR long, ASBUILT long, ACCURACY char(20), LENGTH number(10,3), STARTID number(11,0), ENDID number(11,0), PIPEID number(11,0), GID number(11,0)
    -> DateFormatter
DateFormatter
    SRCFMT = Unknown - Automatic Detection
    DATE_ATTR = YEAR
    INVALID_DATE_VALUE = 0001-01-01
    FMT = ISO Date (%Y-%m-%d)
    -> AttributeValueMapper
FeatureMerger_8
    MERGE_TYPE = Attributes Only
    SUPPLIERS_FIRST = No
    IGNORE_NULLS = No
    PROCESS_DUPS = No
    REJECT_NULL_MISSING_KEYS = No
    JOIN_KEYS = 1 1 AUTO
    ATTR_ACCUM_MODE = Merge Supplier
    ATTR_CONFLICT_RES = Use Requestor
    MERGED -> TopologyBuilder
TopologyBuilder
    DEAGGREGATE_INPUT = Yes
    BOUNDING_EDGES = All
    OVERLAPPING_MODE = No
    ALLOW_CYCLES = No
    MAX = 0
    PROP_ATTRS = No
    CLEAN_DATA = Yes
    NODE -> FeatureMerger [REQUESTOR]
    LINE -> UUIDGenerator

Bookmark: Remap attributes
AttributeValueMapper
    LUT = Primary Supply,supplyLine,Primary Distribution,mainLine,Secondary Distributi,mainLine,Secondary Supply,supplyLine,Service Line,houseServiceLine
    DIRECTION = Forward (Source To Destination)
    VAL_ATTR = TYPE
    SRC = TYPE
    -> AttributeValueMapper_2
AttributeValueMapper_2
    LUT = HDPE,PE,AC,concrete,PE,PE,ST,steel,VC,clay,CSP,steel,DI,iron,PVC,PVC,Unknown,unknown,PERF,perforated,RCON,RCON,UN,unknown,CU,copper
    DIRECTION = Forward (Source To Destination)
    VAL_ATTR = MATERIAL
    SRC = MATERIAL
    DEFAULT_VALUE = unknown
    -> AttributeValueMapper_3
AttributeValueMapper_3
    LUT = ASBUILT,assumed,FIELD,surveyed,GPS,surveyed,ORTHOPHOTO,estimated,TEMPEST,estimated,Unknown,unknown,UNKNOWN,unknown
    DIRECTION = Forward (Source To Destination)
    VAL_ATTR = ACCURACY
    SRC = ACCURACY
    DEFAULT_VALUE = unknown
    -> FeatureMerger_8 [REQUESTOR]
    -> AttributeFilter_2

Bookmark: Remap attributes
AttributeValueMapper_4
    LUT = ASBUILT,assumed,FIELD,surveyed,GPS,surveyed,ORTHOPHOTO,estimated,TEMPEST,estimated,Unknown,unknown,UNKNOWN,unknown
    DIRECTION = Forward (Source To Destination)
    VAL_ATTR = ACCURACY
    SRC = ACCURACY
    DEFAULT_VALUE = unknown
    -> TopologyBuilder_2

Bookmark: Create Network, NetworkGraph & LiquidMedium
Note: The NetworkID and NetworkGraphID are needed in lots of other places in the workbench. These connections go to a series of FeatureMergers to deliver the IDs where needed.
Creator_3
    GEOMTYPE = Geometry Object
    NUM = 1
    CREATED -> UUIDGenerator_2
Note: Set function & usage = distribution
AttributeCreator_5
    ATTR_TABLE:
      SET_TO utility_usage{0} = distribution
      SET_TO utility_function{0} = distribution
    -> AttributeRenamer_3
Note: Set the network ID as the gml_id / Also set the transportedMedium to be the LiquidMedium ID
AttributeRenamer_3
    ATTR_TABLE = RENAME_SET_DEFAULT Network_ID > gml_id
    -> Network (writer CITYGML_1)
Note: Set feature role as transportedMedium. / Also set transportedMedium to be freshWater + its properties
AttributeCreator_9
    ATTR_TABLE:
      SET_TO citygml_feature_role = transportedMedium
      SET_TO utility_type = freshWater
      SET_TO utility_is_corrosive = false
      SET_TO utility_is_explosive = false
      SET_TO utility_flammable = 0
    -> AttributeRenamer_10
Note: Set LiquidMedium ID as gml_id / Also set NetworkID as parent_gml_id
AttributeRenamer_10
    ATTR_TABLE:
      RENAME_SET_DEFAULT LiquidMedium_ID > gml_id
      RENAME_SET_DEFAULT Network_ID > gml_parent_id
    -> LiquidMedium (writer CITYGML_1)
Note: Set relationship between Network / and NetworkGraph (+topoGraph)
AttributeCreator_24
    ATTR_TABLE = SET_TO citygml_feature_role = topoGraph
    -> AttributeRenamer_2
Note: Set gml_id as NetworkGraph_ID / and gml_parent_id as NetworkGraph_ID
AttributeRenamer_2
    ATTR_TABLE:
      RENAME_SET_DEFAULT NetworkGraph_ID > gml_id
      RENAME_SET_DEFAULT Network_ID > gml_parent_id
    -> NetworkGraph (writer CITYGML_1)

Bookmark: Network ID
UUIDGenerator_2
    UUID_ATTR = Network_ID
    -> StringConcatenator_2
StringConcatenator_2
    ATTRLIST = Network_ID
    ACTION = Overwrite Existing Attributes
    PARM_LINE = NetworkID_@Value(Network_ID)
    -> UUIDGenerator_3

Bookmark: NetworkGraph ID
UUIDGenerator_3
    UUID_ATTR = NetworkGraph_ID
    -> StringConcatenator_3
StringConcatenator_3
    ATTRLIST = NetworkGraph_ID
    ACTION = Overwrite Existing Attributes
    PARM_LINE = NetworkGraphID_@Value(NetworkGraph_ID)
    -> FeatureMerger_9 [SUPPLIER]
    -> UUIDGenerator_7
    -> FeatureMerger_8 [SUPPLIER]
    -> FeatureMerger [SUPPLIER]

Bookmark: LiquidMedium ID
UUIDGenerator_7
    UUID_ATTR = LiquidMedium_ID
    -> StringConcatenator_7
StringConcatenator_7
    ATTRLIST = LiquidMedium_ID
    ACTION = Overwrite Existing Attributes
    PARM_LINE = LiquidMediumID_@Value(LiquidMedium_ID)
    -> AttributeCreator_5
    -> AttributeCreator_9
    -> AttributeCreator_24

Bookmark: RoundPipe ID
UUIDGenerator
    UUID_ATTR = RoundPipe_ID
    -> StringConcatenator
StringConcatenator
    ATTRLIST = RoundPipe_ID
    ACTION = Overwrite Existing Attributes
    PARM_LINE = RoundPipeID_@Value(RoundPipe_ID)
    -> UUIDGenerator_4

Bookmark: InteriorFeatureLink ID
UUIDGenerator_4
    UUID_ATTR = InteriorFeatureLink_ID
    -> StringConcatenator_4
StringConcatenator_4
    ATTRLIST = InteriorFeatureLink_ID
    ACTION = Overwrite Existing Attributes
    PARM_LINE = InteriorFeatureLinkID_@Value(InteriorFeatureLink_ID)
    -> UUIDGenerator_5

Bookmark: FeatureGraph ID
UUIDGenerator_5
    UUID_ATTR = FeatureGraph_ID
    -> StringConcatenator_5
StringConcatenator_5
    ATTRLIST = FeatureGraph_ID
    ACTION = Overwrite Existing Attributes
    PARM_LINE = FeatureGraphID_@Value(FeatureGraph_ID)
    -> SurfaceDraper [DRAPE_FEATURES]
    -> GeometryRemover_5
    -> FeatureMerger_3 [REQUESTOR]
    -> DuplicateFilter

Bookmark: Create RoundPipes, FeatureGraphs, InteriorFeatureLinks and ExteriorMaterials
Note: Make list of unique MATERIAL values / from source data
DuplicateFilter
    INPUT_ORDERED_CHOICE = No
    KEYATTR = MATERIAL
    UNIQUE -> UUIDGenerator_8
Note: Create attribute utility_type / and use the existing MATERIAL / attribute
AttributeCreator_10
    ATTR_TABLE = SET_TO utility_type = @Value(MATERIAL)
    -> AttributeRenamer_12
Note: Set gml_id as ExteriorMaterialID
AttributeRenamer_12
    ATTR_TABLE = RENAME_SET_DEFAULT ExteriorMaterial_ID > gml_id
    -> ExteriorMaterial (writer CITYGML_1)
Note: Remove Geometry because it is / irrelevant for FeatureGraphs
GeometryRemover_5
    -> AttributeCreator_4
Note: Set relationship between FeatureGraph / and NetworkGraph (+featureGraphMember)
AttributeCreator_4
    ATTR_TABLE = SET_TO citygml_feature_role = featureGraphMember
    -> AttributeRenamer_4
Note: Set gml_id (FeatureGraph_ID) / and gml_parent_id (NetworkGraph_ID)
AttributeRenamer_4
    ATTR_TABLE:
      RENAME_SET_DEFAULT FeatureGraph_ID > gml_id
      RENAME_SET_DEFAULT NetworkGraph_ID > gml_parent_id
    -> FeatureGraph (writer CITYGML_1)
    -> FeatureMerger_15 [SUPPLIER]
FeatureMerger
    MERGE_TYPE = Attributes Only
    SUPPLIERS_FIRST = No
    IGNORE_NULLS = No
    PROCESS_DUPS = No
    REJECT_NULL_MISSING_KEYS = No
    JOIN_KEYS = 1 1 AUTO
    ATTR_ACCUM_MODE = Merge Supplier
    ATTR_CONFLICT_RES = Use Requestor
    MERGED -> ListExploder
Note: Set relationship between FeatureGraph / and InteriorFeatureLink (+linkMember)
AttributeCreator_6
    ATTR_TABLE = SET_TO citygml_feature_role = linkMember
    -> AttributeRenamer_8
Note: Set gml_id (InteriorFeatureLink ID) / Also set gml_parent_id (FeatureGraph)
AttributeRenamer_8
    ATTR_TABLE:
      RENAME_SET_DEFAULT InteriorFeatureLink_ID > gml_id
      RENAME_SET_DEFAULT FeatureGraph_ID > gml_parent_id
    -> InteriorFeatureLink (writer CITYGML_1)
GEOTIFF (reader GEOTIFF_1)
    attributes: datatype char(255)
    -> SurfaceDraper [POINTS/LINES]
SurfaceDraper
    DRAPE_TYPE = VERTEX
    TOLERANCE = -2
    INTERPOLATION_TYPE = AUTO
    ADDZ_TYPE = Replace Z
    DRAPED_FEATURES -> Offsetter
Offsetter
    MODE = Cartesian Coordinate
    YOFF = 0
    ZOFF = -2
    XOFF = 0
    OFFSET -> AttributeCreator_2
AttributeCreator_2
    ATTR_TABLE:
      SET_TO citygml_lod_name = lod1Geometry
      SET_TO utility_has_material{0}.xlink_href = hasMaterial
    -> GeometryPropertySetter
GeometryPropertySetter
    SRC_ATTRS = citygml_lod_name
    SETTYPE_PARAM = Traits From Attributes
    REMOVE_ATTRIBUTE = No
    OVERWRITE_CHOICE = Yes
    SET -> AttributeCreator
Note: Set relationship between RoundPipe / and Network (+component)
AttributeCreator
    ATTR_TABLE = SET_TO citygml_feature_role = component
    -> AttributeRenamer
Note: Set gml_id as RoundPipeID / and gml_parent_id as NetworkID
AttributeRenamer
    ATTR_TABLE:
      RENAME_SET_DEFAULT Network_ID > gml_parent_id
      RENAME_SET_DEFAULT RoundPipe_ID > gml_id
    -> FeatureMerger_7 [REQUESTOR]
Note: Map the ExteriorMaterial to the / RoundPipes
FeatureMerger_7
    MERGE_TYPE = Attributes Only
    SUPPLIERS_FIRST = No
    IGNORE_NULLS = No
    PROCESS_DUPS = No
    REJECT_NULL_MISSING_KEYS = No
    JOIN_KEYS = @Value(MATERIAL) @Value(MATERIAL) AUTO
    ATTR_ACCUM_MODE = Merge Supplier
    ATTR_CONFLICT_RES = Use Requestor
    MERGED -> AttributeRenamer_11
Note: Set relationship between RoundPipes / and ExteriorMaterials via Xlink
AttributeRenamer_11
    ATTR_TABLE:
      RENAME_SET_DEFAULT ExteriorMaterial_ID > utility_has_material{0}.xlink_href
      RENAME_SET_DEFAULT TYPE > utility_class
      RENAME_SET_DEFAULT YEAR > utility_year_of_construction
      RENAME_SET_DEFAULT ACCURACY > utility_location_quality
    -> FeatureMerger_15 [REQUESTOR]
FeatureMerger_15
    MERGE_TYPE = Attributes Only
    SUPPLIERS_FIRST = No
    IGNORE_NULLS = No
    PROCESS_DUPS = No
    REJECT_NULL_MISSING_KEYS = No
    JOIN_KEYS = @Value(RoundPipe_ID) @Value(RoundPipe_ID) AUTO
    ATTR_ACCUM_MODE = Merge Supplier
    ATTR_CONFLICT_RES = Use Requestor
    MERGED -> AttributeRenamer_13
AttributeRenamer_13
    ATTR_TABLE = RENAME_SET_DEFAULT FeatureGraph_ID > utility_topo_graph_xlink_href
    -> RoundPipe (writer CITYGML_1)

Bookmark: ExteriorMaterial ID
UUIDGenerator_8
    UUID_ATTR = ExteriorMaterial_ID
    -> StringConcatenator_8
StringConcatenator_8
    ATTRLIST = ExteriorMaterial_ID
    ACTION = Overwrite Existing Attributes
    PARM_LINE = ExteriorMaterialID_@Value(ExteriorMaterial_ID)
    -> FeatureMerger_7 [SUPPLIER]
    -> AttributeCreator_10

Bookmark: Node IDs
Note: 1. Each node contains a list which lists all lines (i.e. the corresponding arc_ids) that are connected with the node. / This list is split up here so that each node is connected to one line only. / The number of nodes duplicates analogously to the number of lines connected with a node.
ListExploder
    ATTR_ACCUM_MODE = Merge Incoming List
    LIST_ATTR = _node_angle{}
    ATTR_CONFLICT_RES = Use Incoming List
    INDEX_ATTR = _element_index
    ELEMENTS -> ExpressionEvaluator
Note: Arc_ids with a negative sign are / turned into positive numbers here.
ExpressionEvaluator
    ATTRLIST = fme_arc_id
    ACTION = Overwrite Existing Attributes
    EXPRESSION = @abs(@Value(fme_arc_id))
    -> UUIDGenerator_6
FeatureMerger_5
    MERGE_TYPE = Attributes Only
    SUPPLIERS_FIRST = No
    IGNORE_NULLS = No
    PROCESS_DUPS = No
    REJECT_NULL_MISSING_KEYS = No
    JOIN_KEYS = @Value(Node_ID) @Value(utility_start_xlink_href) AUTO
    ATTR_ACCUM_MODE = Merge Supplier
    ATTR_CONFLICT_RES = Use Requestor
    MERGED -> AttributeCreator_11
    NOT_MERGED -> FeatureMerger_6 [REQUESTOR]
FeatureMerger_6
    MERGE_TYPE = Attributes Only
    SUPPLIERS_FIRST = No
    IGNORE_NULLS = No
    PROCESS_DUPS = No
    REJECT_NULL_MISSING_KEYS = No
    JOIN_KEYS = @Value(Node_ID) @Value(utility_end_xlink_href) AUTO
    ATTR_ACCUM_MODE = Merge Supplier
    ATTR_CONFLICT_RES = Use Requestor
    MERGED -> AttributeCreator_11
Note: Set type = exterior
AttributeCreator_11
    ATTR_TABLE = SET_TO utility_type = exterior
    -> 3DForcer_3
Note: Set relation between FeatureGraph / and Node (+nodeMember)
AttributeCreator_8
    ATTR_TABLE = SET_TO citygml_feature_role = nodeMember
    -> AttributeRenamer_9
Note: Set gml_id to Node_ID / and gml_parent_id to FeatureGraph_ID
AttributeRenamer_9
    ATTR_TABLE:
      RENAME_SET_DEFAULT Node_ID > gml_id
      RENAME_SET_DEFAULT FeatureGraph_ID > gml_parent_id
    -> Node (writer CITYGML_1)

Bookmark: Node ID
UUIDGenerator_6
    UUID_ATTR = Node_ID
    -> StringConcatenator_6
StringConcatenator_6
    ATTRLIST = Node_ID
    ACTION = Overwrite Existing Attributes
    PARM_LINE = NodeID_@Value(Node_ID)
    -> FeatureMerger_3 [SUPPLIER]
    -> FeatureMerger_4 [SUPPLIER]
    -> FeatureMerger_5 [REQUESTOR]
    -> FeatureMerger_14 [REQUESTOR]
    -> FeatureMerger_14 [SUPPLIER]
    -> AttributeRenamer_26

Bookmark: Connect InteriorFeatureLinks with Nodes
Note: Connect InteriorFeatureLinks with Nodes. / Now InteriorFeatureLinks have attributes of Nodes / So InteriorFeatureLinks can have a reference to a start Node
FeatureMerger_3
    MERGE_TYPE = Attributes Only
    SUPPLIERS_FIRST = No
    IGNORE_NULLS = No
    PROCESS_DUPS = No
    REJECT_NULL_MISSING_KEYS = No
    JOIN_KEYS = @Value(_edge_id) @Value(fme_arc_id) AUTO @Value(_from_node) @Value(_node_number) AUTO
    ATTR_ACCUM_MODE = Merge Supplier
    ATTR_CONFLICT_RES = Use Requestor
    MERGED -> AttributeRenamer_6
Note: Set XLink reference between / InteriorFeatureLink and start / nodes
AttributeRenamer_6
    ATTR_TABLE = RENAME_SET_DEFAULT Node_ID > utility_start_xlink_href
    -> FeatureMerger_4 [REQUESTOR]
Note: Connect InteriorFeatureLinks with Nodes. / Now InteriorFeatureLinks have attributes of Nodes / So InteriorFeatureLinks can have a reference to a end Node
FeatureMerger_4
    MERGE_TYPE = Attributes Only
    SUPPLIERS_FIRST = No
    IGNORE_NULLS = No
    PROCESS_DUPS = No
    REJECT_NULL_MISSING_KEYS = No
    JOIN_KEYS = @Value(_edge_id) @Value(fme_arc_id) AUTO @Value(_to_node) @Value(_node_number) AUTO
    ATTR_ACCUM_MODE = Merge Supplier
    ATTR_CONFLICT_RES = Use Requestor
    MERGED -> AttributeRenamer_7
Note: Set XLink reference between / InteriorFeatureLink and end / nodes
AttributeRenamer_7
    ATTR_TABLE = RENAME_SET_DEFAULT Node_ID > utility_end_xlink_href
    -> 3DForcer_2
    -> FeatureMerger_5 [SUPPLIER]
    -> FeatureMerger_6 [SUPPLIER]

Bookmark: Set CityGML Geometry
3DForcer_2
    KEEPZVAL = No
    ZVALATTR = 0
    -> AttributeCreator_3
AttributeCreator_3
    ATTR_TABLE = SET_TO citygml_lod_name = realization
    -> GeometryPropertySetter_2
GeometryPropertySetter_2
    SRC_ATTRS = citygml_lod_name
    SETTYPE_PARAM = Traits From Attributes
    REMOVE_ATTRIBUTE = No
    OVERWRITE_CHOICE = Yes
    SET -> AttributeCreator_6

Bookmark: Set CityGML Geometry
3DForcer_3
    KEEPZVAL = No
    ZVALATTR = 0
    -> AttributeCreator_7
AttributeCreator_7
    ATTR_TABLE = SET_TO citygml_lod_name = realization
    -> GeometryPropertySetter_3
GeometryPropertySetter_3
    SRC_ATTRS = citygml_lod_name
    SETTYPE_PARAM = Traits From Attributes
    REMOVE_ATTRIBUTE = No
    OVERWRITE_CHOICE = Yes
    SET -> AttributeCreator_8

Bookmark: Node IDs
Note: Connect nodes with themselves
FeatureMerger_14
    MERGE_TYPE = Attributes Only
    SUPPLIERS_FIRST = No
    IGNORE_NULLS = No
    PROCESS_DUPS = Yes
    LIST_NAME = _list
    LIST_ATTRS_TO_INCLUDE = _element_index _node_number ACCURACY ASBUILT CATCHMENT DIAMETER ENDID fme_arc_angle fme_arc_id GID LENGTH MATERIAL Node_ID OWNER PIPEID STARTID TYPE WATERCATEG YEAR
    GEOM_TYPE = Build Polygons
    REJECT_NULL_MISSING_KEYS = No
    JOIN_KEYS = @Value(_node_number) @Value(_node_number) AUTO
    ATTR_ACCUM_MODE = Merge Supplier
    ATTR_CONFLICT_RES = Use Requestor
    CONNECT_Z_MODE = First Wins
    MERGED -> AttributeRenamer_22
Note: Rename Node_ID to / Node_ID_original
AttributeRenamer_22
    ATTR_TABLE = RENAME_SET_DEFAULT Node_ID > Node_ID_original
    -> ListExploder_6
Note: See slides for InterFeatureLinks
ListExploder_6
    ATTR_ACCUM_MODE = Merge Incoming List
    LIST_ATTR = _list{}
    ATTR_CONFLICT_RES = Use Original
    INDEX_ATTR = _element_index
    LIST_FOUND -> AttributeRenamer_23
Note: Rename Node_ID to / Node_ID_merged
AttributeRenamer_23
    ATTR_TABLE = RENAME_SET_DEFAULT Node_ID > Node_ID_merged
    -> TestFilter
Note: Keep only nodes for which / Node_ID_original = Node_ID_merged
TestFilter
    TEST_LIST = BOOL_OP,OR,COMPOSITE_TEST,<Unused>,TEST_CLAUSE,"TEST @Value(Node_ID_original) != @Value(Node_ID_merged)",@Value(Node_ID_original) < @Value(Node_ID_merged)
    DEFAULT_VALUE = <UNFILTERED>
    @Value(Node_ID_original) < @Value(Node_ID_merged) -> TestFilter_2
Note: See slides for / InterFeatureLinks
TestFilter_2
    TEST_LIST = BOOL_OP,OR,COMPOSITE_TEST,<Unused>,TEST_CLAUSE,"TEST @Value(Node_ID_original) < @Value(Node_ID_merged)",@Value(Node_ID_original) < @Value(Node_ID_merged)
    DEFAULT_VALUE = <UNFILTERED>
    @Value(Node_ID_original) < @Value(Node_ID_merged) -> UUIDGenerator_14
Note: Rename Node_ID_original to utility_start_xlink_href / and Node_ID_merged to utility_end_xink_href
AttributeRenamer_24
    ATTR_LIST = Node_ID_original,utility_start_xlink_href,,Node_ID_merged,utility_end_xlink_href,
    -> GeometryRemover_3
Note: See slides for InterFeatureLinks
GeometryRemover_3
    -> AttributeCreator_19
Note: Set utility_type = connects
AttributeCreator_19
    ATTR_TABLE = SET_TO utility_type = connects
    -> AttributeCreator_27
Note: Set relationship between InterFeatureLink / and NetworkGraph (+linkMember)
AttributeCreator_27
    ATTR_LIST = citygml_feature_role,linkMember
    -> AttributeRenamer_25
Note: Set gml_id to InterFeatureLink_ID / and gml_parent_id to NetworkGraph_ID
AttributeRenamer_25
    ATTR_LIST = InterFeatureLink_ID,gml_id,,NetworkGraph_ID,gml_parent_id,
    -> InterFeatureLink (writer CITYGML_1)

Bookmark: InterFeatureLink ID
UUIDGenerator_14
    UUID_ATTR = InterFeatureLink_ID
    -> StringConcatenator_14
StringConcatenator_14
    ATTRLIST = InterFeatureLink_ID
    ACTION = Overwrite Existing Attributes
    PARM_LINE = InterFeatureLinkID_@Value(InterFeatureLink_ID)
    -> AttributeRenamer_24

Bookmark: Make 3D Geometry
Note: 1. Drape the points onto the DEM. / 2. Offset the points by -2m in z (down) and 0.001m in x. This is because the TopologyBuilder only works with 2D topology. If there is no change in x or y, the length of the feature disappears and we cannot build an appropriate geometry or featuregraph. / 3. Draw a line between the point and its corresponding offset point with a PointConnector. We now have a (almost) vertical line reaching up to the DEM from underneath, where it is connected to the network.
SurfaceDraper_2
    DRAPE_TYPE = VERTEX
    TOLERANCE = -2
    INTERPOLATION_TYPE = AUTO
    ADDZ_TYPE = Replace Z
    DRAPED_FEATURES -> Offsetter_2
    DRAPED_FEATURES -> PointConnector
Offsetter_2
    MODE = Cartesian Coordinate
    YOFF = 0
    ZOFF = -2
    XOFF = .0001
    OFFSET -> PointConnector
PointConnector
    BREAKATTR = PID
    ACCUM_INPUT_ATTRS = Get Attributes From One Representative Feature
    LINE -> AttributeRenamer_20

Bookmark: InteriorFeatureLink ID
UUIDGenerator_12
    UUID_ATTR = InteriorFeatureLink_ID
    -> StringConcatenator_12
StringConcatenator_12
    ATTRLIST = InteriorFeatureLink_ID
    ACTION = Overwrite Existing Attributes
    PARM_LINE = InteriorFeatureLinkID_@Value(InteriorFeatureLink_ID)
    -> UUIDGenerator_13

Bookmark: RoundPipe ID
UUIDGenerator_13
    UUID_ATTR = RoundPipe_ID
    -> StringConcatenator_13
StringConcatenator_13
    ATTRLIST = RoundPipe_ID
    ACTION = Overwrite Existing Attributes
    PARM_LINE = RoundPipe_@Value(RoundPipe_ID)
    -> UUIDGenerator_15

Bookmark: FeatureGraph ID
UUIDGenerator_15
    UUID_ATTR = FeatureGraph_ID
    -> StringConcatenator_15
StringConcatenator_15
    ATTRLIST = FeatureGraph_ID
    ACTION = Overwrite Existing Attributes
    PARM_LINE = FeatureGraphID_@Value(FeatureGraph_ID)
    -> FeatureMerger_10 [REQUESTOR]
    -> AttributeCreator_17
    -> GeometryRemover_2

Bookmark: Set CityGML Geometry
AttributeCreator_17
    ATTR_TABLE = SET_TO citygml_lod_name = lod1Geometry
    -> GeometryPropertySetter_6
GeometryPropertySetter_6
    SRC_ATTRS = citygml_lod_name
    SETTYPE_PARAM = Traits From Attributes
    REMOVE_ATTRIBUTE = No
    OVERWRITE_CHOICE = Yes
    SET -> AttributeCreator_22

Bookmark: Node ID
UUIDGenerator_11
    UUID_ATTR = Node_ID
    -> StringConcatenator_11
StringConcatenator_11
    ATTRLIST = Node_ID
    ACTION = Overwrite Existing Attributes
    PARM_LINE = NodeID_@Value(Node_ID)
    -> FeatureMerger_10 [SUPPLIER]
    -> FeatureMerger_11 [SUPPLIER]
    -> FeatureMerger_13 [REQUESTOR]
    -> AttributeRenamer_27

Bookmark: Set CityGML Geometry
3DForcer_4
    KEEPZVAL = No
    ZVALATTR = 0
    -> AttributeCreator_12
AttributeCreator_12
    ATTR_TABLE = SET_TO citygml_lod_name = realization
    -> GeometryPropertySetter_4
GeometryPropertySetter_4
    SRC_ATTRS = citygml_lod_name
    SETTYPE_PARAM = Traits From Attributes
    REMOVE_ATTRIBUTE = No
    OVERWRITE_CHOICE = Yes
    SET -> AttributeCreator_13

Bookmark: Set CityGML Geometry
3DForcer_5
    KEEPZVAL = No
    ZVALATTR = 0
    -> AttributeCreator_14
AttributeCreator_14
    ATTR_TABLE = SET_TO citygml_lod_name = realization
    -> GeometryPropertySetter_5
GeometryPropertySetter_5
    SRC_ATTRS = citygml_lod_name
    SETTYPE_PARAM = Traits From Attributes
    REMOVE_ATTRIBUTE = No
    OVERWRITE_CHOICE = Yes
    SET -> AttributeCreator_16

Bookmark: Establish InterFeatureLink at bottom of RoundPipe
Note: We do a spatial join (NeighbourFinder) that will locate the nearest Node from the RoundPipe Nodes to the TerminalElement Nodes, within a very small distance. / Next, we sort them by the "_closest_base_x" attribute, descending. Since we also shifted the lower node of the TerminalElement by 0.001m in the x direction, the one with the greater x is the one wwe want to keep. / Finally, we delete all the duplicates, based on the RoundPipe_Node_ID attribute. Now, we have for each feature, the lower TerminalElement Node, and its corresponding RoundPipe Node.
NeighborFinder
    MAX = 3
    CANDIDATES_FIRST = No
    ATTR_ACCUM_MODE = Merge Candidate
    K = 1
    TREAT_POLYGON_AS = Lines
    ATTR_CONFLICT_RES = Use Base
    MODE = Bases and Candidates
    INSERT_VERTEX = No
    MATCHED -> Sorter
Sorter
    SORT_PARM = _closest_base_x NUMERIC DESCENDING
    SORTED -> DuplicateFilter_2
DuplicateFilter_2
    INPUT_ORDERED_CHOICE = Yes
    KEYATTR = RoundPipe_Node_ID
    UNIQUE -> UUIDGenerator_16

Bookmark: InterFeatureLink ID
UUIDGenerator_16
    UUID_ATTR = InterFeatureLink_ID
    -> StringConcatenator_16
StringConcatenator_16
    ATTRLIST = InterFeatureLink_ID
    ACTION = Overwrite Existing Attributes
    PARM_LINE = InterFeatureLinkID_@Value(InterFeatureLink_ID)
    -> AttributeRenamer_29
